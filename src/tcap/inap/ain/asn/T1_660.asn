AIN-Operations
DEFINITIONS ::=
BEGIN
IMPORTS
OPERATION,
ERROR
FROM TCAPPackage{iso memberbody usa t1-114};

ProviderInstruction ::= OPERATION
ARGUMENT ProviderInstructionArg
ERRORS
{ 
  applicationError
}

ProviderInstructionArg ::=SET {
endUserNumber            [10] ServiceKey,
callingPartyAni          [4]IMPLICIT Digits,
cgpLata                  [4]IMPLICIT Digits,
oli                      [PRIVATE 37] IMPLICIT OriginatingStationType,
cicSupport               [PRIVATE 72] IMPLICIT CICExpansion OPTIONAL         
}

ConnetionControl ::= OPERATION
ARGUMENT ConnectionControlArg
ERRORS
{ 
  applicationError
}

ConnectionControlArg ::=SET {
networkRoutingNumber         [4] IMPLICIT Digits,
carrierId                    [4] IMPLICIT Digits,
billingIndicators            [PRIVATE 33] IMPLICIT Digits
}

ServiceKey ::=CHOICE{
 digits [4]IMPLICIT Digits
}

OriginatingStationType ::= OCTET STRING
CICExpansion ::= ENUMERATED{
expandedCICSupport    (1)
}

-- ERRORS{
-- unexpectedComponentSequence,
-- unexpectedDataValue,
-- dataUnavailable
-- }
-- LINKED{
-- connectionControl
-- }
-- }

--unexpectedComponentSequence ::= SET{}

--::= nationalError 1
--UnexpectedDataValue ::= ERROR 
--ARGUMENT UnexpectedDataValueArg

UnexpectedDataValue ::= SET{
unexpectedValue  ProblemData
} 

-- ::= nationalError 2
-- dataUnavailable ::= SET{}
-- ::= nationalError 6

Digits ::= OCTET STRING

ProblemData ::= [6] IMPLICIT OCTET STRING

END
