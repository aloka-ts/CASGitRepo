IN-CS2-SSF-SCF-ops-args {itu-t recommendation q 1228 modules(0) in-cs2-ssf-scf-ops-args (5) version1(0)}
DEFINITIONS IMPLICIT TAGS ::=
BEGIN
IMPORTS
errortypes, datatypes, operationcodes, classes, ros-InformationObjects
FROM IN-CS2-object-identifiers
{itu-t recommendation q 1228 modules(0) in-cs2-object-identifiers(17) version1(0)}
OPERATION
FROM Remote-Operations-Information-Objects ros-InformationObjects
PARAMETERS-BOUND
FROM IN-CS2-classes classes
opcode-activateServiceFiltering,
opcode-activityTest,
opcode-analysedInformation,
opcode-analyseInformation,
opcode-applyCharging,
opcode-applyChargingReport,
opcode-assistRequestInstructions,
opcode-authorizeTermination,
opcode-callGap,
opcode-callInformationReport,
opcode-callInformationRequest,
opcode-cancel,
opcode-cancelStatusReportRequest,
opcode-collectedInformation,
opcode-collectInformation,
opcode-connect,
opcode-connectToResource,
opcode-continue,
opcode-continueWithArgument,
opcode-createCallSegmentAssociation,
opcode-disconnectForwardConnection,
opcode-dFCWithArgument,
opcode-disconnectLeg,
opcode-entityReleased,
opcode-establishTemporaryConnection,
opcode-eventNotificationCharging,
opcode-eventReportBCSM,
opcode-eventReportFacility,
opcode-facilitySelectedAndAvailable,
opcode-furnishChargingInformation,
opcode-holdCallInNetwork,
opcode-initialDP,
opcode-initiateCallAttempt,
opcode-manageTriggerData,
opcode-mergeCallSegments,
opcode-moveCallSegments,
opcode-oAbandon,
opcode-oAnswer,
opcode-oCalledPartyBusy,
opcode-oDisconnect,
opcode-oMidCall,
opcode-moveLeg,
opcode-oNoAnswer,
opcode-originationAttempt,
opcode-originationAttemptAuthorized,
opcode-oSuspended,
opcode-reconnect,
opcode-releaseCall,
opcode-reportUTSI,
opcode-requestCurrentStatusReport,
opcode-requestEveryStatusChangeReport,
opcode-requestFirstStatusMatchReport,
opcode-requestNotificationChargingEvent,
opcode-requestReportBCSMEvent,
opcode-requestReportUTSI,
opcode-requestReportFacilityEvent,
opcode-resetTimer,
opcode-routeSelectFailure,
opcode-selectFacility,
opcode-selectRoute,
opcode-sendChargingInformation,
opcode-sendFacilityInformation,
opcode-sendSTUI,
opcode-serviceFilteringResponse,
opcode-splitLeg,
opcode-statusReport,
opcode-tAnswer,
opcode-tBusy,
opcode-tDisconnect,
opcode-termAttemptAuthorized,
opcode-terminationAttempt,
opcode-tMidCall,
opcode-tNoAnswer,
opcode-tSuspended
FROM IN-CS2-operationcodes operationcodes
AccessCode ,
ActionIndicator,
ActionPerformed,
AChBillingChargingCharacteristics ,
AdditionalCallingPartyNumber ,
AlertingPattern,
ApplicationTimer,
AssistingSSPIPRoutingAddress ,
BackwardGVNS ,
BCSMEvent ,
BearerCapability ,
CalledPartyBusinessGroupID,
CalledPartyNumber ,
CalledPartySubaddress,
CallingPartyBusinessGroupID,
CallingPartyNumber ,
CallingPartysCategory,
CallingPartySubaddress,
CallProcessingOperationCorrelationID,
CallResult ,
CallSegmentID ,
Carrier,
Cause ,
CGEncountered,
ChargeNumber ,
ChargingEvent ,
Component,
ComponentCorrelationID,
ComponentType,
ControlType,
CorrelationID ,
CountersValue,
CSAID ,
CutAndPaste,
DateAndTime,
DestinationRoutingAddress ,
Digits ,
DisplayInformation ,
DpSpecificCommonParameters ,
Duration,
EventSpecificInformationBCSM ,
EventSpecificInformationCharging ,
EventTypeBCSM,
EventTypeCharging ,
ExtensionField ,
FacilityGroup,
FacilityGroupMember,
FCIBillingChargingCharacteristics ,
FeatureCode ,
FeatureRequestIndicator,
FilteredCallTreatment ,
FilteringCharacteristics,
FilteringCriteria ,
FilteringTimeOut,
ForwardCallIndicators,
ForwardGVNS ,
ForwardingCondition,
GapCriteria ,
GapIndicators,
GapTreatment ,
GenericName ,
GenericNumbers ,
HighLayerCompatibility,
HoldCause,
initialCallSegment,
INServiceCompatibilityIndication ,
INServiceCompatibilityResponse,
Integer4,
InvokeID,
IPAvailable ,
IPRoutingAddress ,
IPSSPCapabilities ,
ISDNAccessRelatedInformation,
LegID,
leg1,
LocationNumber ,
MiscCallInfo,
MonitorMode,
NumberingPlan,
OriginalCalledPartyID ,
Reason ,
RedirectingPartyID ,
RedirectionInformation,
RegistratorIdentifier,
ReportCondition,
RequestedInformationList ,
RequestedInformationTypeList,
RequestedUTSIList ,
ResourceID ,
ResourceStatus,
ResponseCondition,
RouteList ,
ScfID ,
SCIBillingChargingCharacteristics ,
ServiceInteractionIndicators ,
ServiceInteractionIndicatorsTwo,
ServiceKey,
ServiceProfileIdentifier,
TerminalType,
TimerID,
TimerValue,
TravellingClassMark ,
TriggerDataIdentifier ,
TriggerType,
USIInformation ,
USIServiceIndicator 
FROM IN-CS2-datatypes datatypes
cancelFailed,
eTCFailed,
improperCallerResponse,
missingCustomerRecord,
missingParameter,
parameterOutOfRange,
requestedInfoError,
systemFailure,
taskRefused,
unavailableResource,
unexpectedComponentSequence,
unexpectedDataValue,
unexpectedParameter,
unknownLegID,
unknownResource
FROM IN-CS2-errortypes errortypes
;

-- Rajeev, right way of defining Operation is as below
-- Secondly, compilation will break if OPERATION name doesn;t starts with capital letter
-- like instead of activateServiceFiltering to ActivateServiceFiltering
-- RETURN RESULT is not supported
-- CODE MACRO not supported
--ActivateServiceFiltering OPERATION ::={

ActivateServiceFiltering ::= OPERATION
ARGUMENT ActivateServiceFilteringArg 
-- RETURN RESULT TRUE
ERRORS {missingParameter ,
parameterOutOfRange ,
systemFailure ,
taskRefused ,
unexpectedComponentSequence ,
unexpectedParameter
}
-- Direction: SCF ® SSF, Timer: Tasf
-- When receiving this operation, the SSF handles calls to destination in a specified manner
-- without sending queries for every detected call. It is used for example for providing
-- televoting or mass calling services. Simple registration functionality (counters) and
-- announcement control may be located at the SSF. The operation initializes the specified
-- counters in the SSF.
ActivateServiceFilteringArg ::= SEQUENCE {
filteredCallTreatment [0] FilteredCallTreatment ,
filteringCharacteristics [1] FilteringCharacteristics,
filteringTimeOut [2] FilteringTimeOut ,
filteringCriteria [3] FilteringCriteria ,
startTime [4] DateAndTime OPTIONAL,
extensions [5] SEQUENCE SIZE(1..numOfExtensions) OF
ExtensionField OPTIONAL
}

ActivityTest ::= OPERATION

-- Direction: SCF ® SSF, Timer: Tat
-- This operation is used to check for the continued existence of a relationship between the SCF
-- and SSF. If the relationship is still in existence, then the SSF will respond. If no reply is
-- received, then the SCF will assume that the SSF has failed in some way and will take the
-- appropriate action.
AnalysedInformation ::= OPERATION
ARGUMENT AnalysedInformationArg 
ERRORS {missingCustomerRecord,
missingParameter,
parameterOutOfRange,
systemFailure,
taskRefused,
unexpectedComponentSequence,
unexpectedDataValue,
unexpectedParameter}

-- Direction: SSF ® SCF, Timer: Tadi
-- This operation is used to indicate availability of routing address and call type. (DP –
-- Analysed_Info).
-- For additional information on this operation and its use with open numbering plans, refer to
-- Rec.Q.1224.
AnalysedInformationArg ::= SEQUENCE {
dpSpecificCommonParameters [0] DpSpecificCommonParameters ,
dialledDigits [1] CalledPartyNumber OPTIONAL,
callingPartyBusinessGroupID [2] CallingPartyBusinessGroupID OPTIONAL,
callingPartySubaddress [3] CallingPartySubaddress OPTIONAL,
callingFacilityGroup [4] FacilityGroup OPTIONAL,
callingFacilityGroupMember [5] FacilityGroupMember OPTIONAL,
originalCalledPartyID [6] OriginalCalledPartyID OPTIONAL,
prefix [7] Digits OPTIONAL,
redirectingPartyID [8] RedirectingPartyID OPTIONAL,
redirectionInformation [9] RedirectionInformation OPTIONAL,
routeList [10] RouteList OPTIONAL,
travellingClassMark [11] TravellingClassMark OPTIONAL,
extensions [12] SEQUENCE SIZE(1..numOfExtensions) OF
ExtensionField OPTIONAL,
featureCode [13] FeatureCode OPTIONAL,
accessCode [14] AccessCode OPTIONAL,
carrier [15] Carrier OPTIONAL,
componentType [16] ComponentType OPTIONAL,
component [17] Component OPTIONAL,
componentCorrelationID [18] ComponentCorrelationID OPTIONAL

}
-- For the OPTIONAL parameters, refer to clause 17 for the trigger detection point processing rules
-- to specify when these parameters are included in the message.
AnalyseInformation ::= OPERATION
ARGUMENT AnalyseInformationArg 
-- RETURN RESULT FALSE
ERRORS {missingParameter ,
parameterOutOfRange ,
systemFailure ,
taskRefused ,
unexpectedComponentSequence ,
unexpectedDataValue ,
unexpectedParameter}

-- Direction: SCF ® SSF, Timer: Tai
-- This operation is used to request the SSF to perform the originating basic call processing actions
-- to analyse destination information that is either collected from a calling party or provided by the SCF
-- (e.g. for number translation). This includes actions to validate the information according to an office
-- or customized dialling plan, and if valid, to determine call termination information, to include the called
-- party address, the type of call (e.g. intranetwork or internetwork), and carrier (if internetwork).
-- If the called party is not served by the SSF, the SSF also determines a route index based on the called
-- party address and class of service, where the route index points to a list of outgoing trunk groups.
AnalyseInformationArg ::= SEQUENCE {
destinationRoutingAddress [0] DestinationRoutingAddress ,
alertingPattern [1] AlertingPattern OPTIONAL,
iSDNAccessRelatedInformation [2] ISDNAccessRelatedInformation OPTIONAL,
originalCalledPartyID [3] OriginalCalledPartyID OPTIONAL,
extensions [4] SEQUENCE SIZE(1..numOfExtensions) OF
ExtensionField OPTIONAL,
callingPartyNumber [5] CallingPartyNumber OPTIONAL,
callingPartysCategory [6] CallingPartysCategory OPTIONAL,
calledPartyNumber [7] CalledPartyNumber OPTIONAL,
chargeNumber [8] ChargeNumber OPTIONAL,
travellingClassMark [9] TravellingClassMark OPTIONAL,
carrier [10] Carrier OPTIONAL,
serviceInteractionIndicators [11] ServiceInteractionIndicators OPTIONAL,
iNServiceCompatibilityResponse [12] INServiceCompatibilityResponse OPTIONAL,
forwardGVNS [13] ForwardGVNS OPTIONAL,
backwardGVNS [14] BackwardGVNS OPTIONAL,
serviceInteractionIndicatorsTwo [15] ServiceInteractionIndicatorsTwo OPTIONAL,
correlationID [16] CorrelationID OPTIONAL,
scfID [17] ScfID OPTIONAL,
callSegmentID [18] CallSegmentID OPTIONAL,
legToBeCreated [19] LegID OPTIONAL

}
ApplyCharging ::= OPERATION
ARGUMENT ApplyChargingArg 
-- RETURN RESULT FALSE
ERRORS {missingParameter ,
unexpectedComponentSequence ,
unexpectedParameter ,
unexpectedDataValue ,
parameterOutOfRange ,
systemFailure ,
taskRefused,
unknownLegID}

-- Direction: SCF ® SSF, Timer: Tac
-- This operation is used for interacting from the SCF with the SSF charging mechanisms. The ApplyChargingReport
-- operation provides the feedback from the SSF to the SCF.
ApplyChargingArg ::= SEQUENCE {
aChBillingChargingCharacteristics [0] AChBillingChargingCharacteristics ,
partyToCharge [2] LegID OPTIONAL,
extensions [3] SEQUENCE SIZE (1..numOfExtensions) OF
ExtensionField OPTIONAL

}
-- The partyToCharge parameter indicates the party in the call to which the ApplyCharging operation
-- should be applied. If it is not present, then it is applied to the A-party
ApplyChargingReport ::= OPERATION
ARGUMENT ApplyChargingReportArg 
--RETURN RESULT FALSE
ERRORS {missingParameter ,
unexpectedComponentSequence ,
unexpectedParameter ,
unexpectedDataValue ,
parameterOutOfRange ,
systemFailure ,
taskRefused}

-- Direction: SSF ® SCF, Timer: Tacr
-- This operation is used by the SSF to report to the SCF the occurrence of a specific charging event
-- as requested by the SCF using the ApplyCharging operation
ApplyChargingReportArg ::= CallResult 
-- NOTE – When the SSF sends the ApplyChargingReport operation as the last event from the Call Segment, the
-- lastEventIndicator parameter such as the CallInformationReport operation is needed for indicating whether
-- the event is last to the SCF. However, because there is no consideration for the parameter expansion in the
-- CS-1, this parameter cannot be added. There are two alternatives for the solution. One is to be included
-- into the CallResult parameter. And the other is to specify a new operation with this parameter. The latter is
-- ffs.
AssistRequestInstructions ::= OPERATION
ARGUMENT AssistRequestInstructionsArg 
--  RETURN RESULT FALSE
ERRORS {missingCustomerRecord,
missingParameter ,
systemFailure ,
taskRefused ,
unexpectedComponentSequence ,
unexpectedDataValue ,
unexpectedParameter}

-- Direction: SSF ® SCF or SRF ® SCF, Timer: Tari
-- This operation is used when there is an assist or a hand-off procedure and may be sent by the SSF
-- or SRF to the SCF. This operation is sent by the assisting SSF to SCF, when the initiating SSF has
-- set up a connection to the SRF or to the assisting SSF as a result of receiving an EstablishTemporaryConnection
-- or Connect/SelectRoute operation (in the case of hand-off) from the SCF.
-- Refer to clause 17 for a description of the procedures associated with this operation.
AssistRequestInstructionsArg ::= SEQUENCE {
correlationID [0] CorrelationID ,
iPAvailable [1] IPAvailable OPTIONAL,
iPSSPCapabilities [2] IPSSPCapabilities OPTIONAL,
extensions [3] SEQUENCE SIZE(1..numOfExtensions) OF
ExtensionField OPTIONAL
}
-- OPTIONAL denotes network-operator specific use. The value of the correlationID may be the
-- Called Party Number supplied by the initiating SSF.
AuthorizeTermination ::= OPERATION
ARGUMENT AuthorizeTerminationArg 
-- RETURN RESULT FALSE
ERRORS {missingParameter ,
systemFailure ,
taskRefused ,
unexpectedComponentSequence ,
unexpectedDataValue ,
unexpectedParameter}

-- Direction: SCF ® SSF, Timer: Tatr
-- This operation is used to request the SSF to resume terminating call processing action at the
-- Authorize_Termination PIC of the call based on the information received from the SCF.
-- For additional information on this operation, refer to Rec. Q.1224.
AuthorizeTerminationArg ::= SEQUENCE {
alertingPattern [0] AlertingPattern OPTIONAL,
callingPartyNumber [1] CallingPartyNumber OPTIONAL,
destinationNumberRoutingAddress [2] CalledPartyNumber OPTIONAL,
displayInformation [3] DisplayInformation OPTIONAL,
iSDNAccessRelatedInformation [4] ISDNAccessRelatedInformation OPTIONAL,
originalCalledPartyID [5] OriginalCalledPartyID OPTIONAL,
travellingClassMark [6] TravellingClassMark OPTIONAL,
extensions [7] SEQUENCE SIZE(1..numOfExtensions) OF
ExtensionField OPTIONAL,
iNServiceCompatibilityResponse [8] INServiceCompatibilityResponse OPTIONAL,
forwardGVNS [9] ForwardGVNS OPTIONAL,
backwardGVNS [10] BackwardGVNS OPTIONAL,
legID [11] LegID OPTIONAL
}
-- OPTIONAL parameters are only provided if modifications are desired to basic call processing values.
CallGap ::= OPERATION
ARGUMENT CallGapArg 
-- RETURN RESULT FALSE
--ALWAYS RESPONDS FALSE

-- Direction: SCF ® SSF, Timer: Tcg
-- This operation is used to request the SSF to reduce the rate at which specific service requests are sent to
-- the SCF. Use of this operation by the SCF to gap queries and updates at the SDF is for further study.
CallGapArg ::= SEQUENCE {
gapCriteria [0] GapCriteria ,
gapIndicators [1] GapIndicators,
controlType [2] ControlType OPTIONAL,
gapTreatment [3] GapTreatment OPTIONAL,
extensions [4] SEQUENCE SIZE(1..numOfExtensions) OF
ExtensionField OPTIONAL
}
-- OPTIONAL denotes network-operator optional. If gapTreatment is not present, the SSF will use
-- a default treatment depending on network-operator implementation.
CallInformationReport ::= OPERATION
ARGUMENT CallInformationReportArg 
-- RETURN RESULT FALSE
--ALWAYS RESPONDS FALSE

-- Direction: SSF ® SCF, Timer: Tcirp
-- This operation is used to send specific call information for a single call to the SCF as requested by the SCF
-- in a previous CallInformationRequest.
CallInformationReportArg ::= SEQUENCE {
requestedInformationList [0] RequestedInformationList ,
correlationID [1] CorrelationID OPTIONAL,
extensions [2] SEQUENCE SIZE(1..numOfExtensions) OF
ExtensionField OPTIONAL,
legID [3] LegID OPTIONAL,
lastEventIndicator [4] BOOLEAN DEFAULT FALSE
}
-- OPTIONAL denotes network-operator optional.
-- The lastEventIndicator parameter is set with ’TRUE’ when the report is last in the Call Segment.
-- In the CS-1, the lastEventIndicator should not be sent, and the meaning of DEFAULT is not applied. The SCF
-- must decide whether the report is last without this parameter.
CallInformationRequest ::= OPERATION
ARGUMENT CallInformationRequestArg 
-- RETURN RESULT FALSE
ERRORS {missingParameter ,
parameterOutOfRange ,
requestedInfoError ,
systemFailure ,
taskRefused ,
unexpectedComponentSequence ,
unexpectedDataValue ,
unexpectedParameter,
unknownLegID}

-- Direction: SCF ® SSF, Timer: Tcirq
-- This operation is used to request the SSF to record specific information about a single call and report it to
-- the SCF (with a CallInformationReport operation).
CallInformationRequestArg ::= SEQUENCE {
requestedInformationTypeList [0] RequestedInformationTypeList,
correlationID [1] CorrelationID OPTIONAL,
extensions [2] SEQUENCE SIZE(1..numOfExtensions) OF
ExtensionField OPTIONAL,
legID [3] LegID OPTIONAL
}
-- OPTIONAL denotes network-operator optional.
Cancel ::= OPERATION
ARGUMENT CancelArg 
-- RETURN RESULT FALSE
ERRORS {cancelFailed ,
missingParameter ,
taskRefused}

-- Direction: SCF ® SSF, or SCF ® SRF, Timer: Tcan
-- This operation cancels the correlated previous operation or all previous requests. The following operations can be
-- cancelled: PlayAnnouncement, PromptAndCollectUserInformation.
CancelArg ::= CHOICE {
invokeID [0] InvokeID,
allRequests [1] NULL,
callSegmentToCancel [2] SEQUENCE {
invokeID [0] InvokeID,
callSegmentID [1] CallSegmentID 
}
}
-- The InvokeID has the same value as that which was used for the operation to be cancelled.
CancelStatusReportRequest ::= OPERATION
ARGUMENT CancelStatusReportRequestArg 
-- RETURN RESULT FALSE
ERRORS {cancelFailed ,
missingParameter ,
taskRefused}

-- Direction: SCF ® SSF, Timer: Tcsr
-- This operation cancels the following processes: RequestFirstStatusMatchReport and
-- RequestEveryStatusChangeReport.
CancelStatusReportRequestArg ::= SEQUENCE {
resourceID [0] ResourceID OPTIONAL,
extensions [1] SEQUENCE SIZE(1..numOfExtensions) OF
ExtensionField OPTIONAL
}

CollectedInformation ::= OPERATION
ARGUMENT CollectedInformationArg 
-- RETURN RESULT FALSE
ERRORS {missingCustomerRecord ,
missingParameter ,
systemFailure ,
taskRefused ,
unexpectedComponentSequence ,
unexpectedDataValue ,
unexpectedParameter}

-- Direction: SSF ® SCF, Timer: Tcdi
-- This operation is used to indicate availability of complete initial information package/dialling string from
-- originating party. (This event may have already occurred in the case of en bloc signalling, in which case
-- the waiting duration in this PIC is zero.) (DP – Collected_Info). For additional information on this operation
-- and its use with open numbering plans, refer to Rec. Q.1224.
CollectedInformationArg ::= SEQUENCE {
dpSpecificCommonParameters [0] DpSpecificCommonParameters ,
dialledDigits [1] CalledPartyNumber OPTIONAL,
callingPartyBusinessGroupID [2] CallingPartyBusinessGroupID OPTIONAL,
callingPartySubaddress [3] CallingPartySubaddress OPTIONAL,
callingFacilityGroup [4] FacilityGroup OPTIONAL,
callingFacilityGroupMember [5] FacilityGroupMember OPTIONAL,
originalCalledPartyID [6] OriginalCalledPartyID OPTIONAL,
prefix [7] Digits OPTIONAL,
redirectingPartyID [8] RedirectingPartyID OPTIONAL,
redirectionInformation [9] RedirectionInformation OPTIONAL,
travellingClassMark [10] TravellingClassMark OPTIONAL,
extensions [11] SEQUENCE SIZE(1..numOfExtensions) OF
ExtensionField OPTIONAL,
featureCode [12] FeatureCode OPTIONAL,
accessCode [13] AccessCode OPTIONAL,
carrier [14] Carrier OPTIONAL,
componentType [15] ComponentType OPTIONAL,
component [16] Component OPTIONAL,
componentCorrelationID [17] ComponentCorrelationID OPTIONAL
}
-- For the OPTIONAL parameters, refer to clause 17 for the trigger detection point processing rules to specify
-- when these parameters are included in the message.
CollectInformation ::= OPERATION
ARGUMENT CollectInformationArg 
-- RETURN RESULT FALSE
ERRORS {missingParameter ,
parameterOutOfRange ,
systemFailure ,
taskRefused ,
unexpectedComponentSequence ,
unexpectedDataValue ,
unexpectedParameter}

-- Direction: SCF ® SSF, Timer: Tci
-- This operation is used to request the SSF to perform the originating basic call processing actions to prompt
-- a calling party for destination information, then collect destination information according to a specified
-- numbering plan (e.g. for virtual private networks).
CollectInformationArg ::= SEQUENCE {
alertingPattern [0] AlertingPattern OPTIONAL,
numberingPlan [1] NumberingPlan OPTIONAL,
originalCalledPartyID [2] OriginalCalledPartyID OPTIONAL,
travellingClassMark [3] TravellingClassMark OPTIONAL,
extensions [4] SEQUENCE SIZE(1..numOfExtensions) OF
ExtensionField OPTIONAL,
callingPartyNumber [5] CallingPartyNumber OPTIONAL,
dialledDigits [6] CalledPartyNumber OPTIONAL,
serviceInteractionIndicators [7] ServiceInteractionIndicators OPTIONAL,
iNServiceCompatibilityResponse [8] INServiceCompatibilityResponse OPTIONAL,
forwardGVNS [9] ForwardGVNS OPTIONAL,
backwardGVNS [10] BackwardGVNS OPTIONAL,
serviceInteractionIndicatorsTwo [11] ServiceInteractionIndicatorsTwo OPTIONAL,
callSegmentID [12] CallSegmentID OPTIONAL,
legToBeCreated [13] LegID OPTIONAL
}

Connect ::= OPERATION
ARGUMENT ConnectArg 
-- RETURN RESULT FALSE
ERRORS {missingParameter ,
parameterOutOfRange ,
systemFailure ,
taskRefused ,
unexpectedComponentSequence ,
unexpectedDataValue ,
unexpectedParameter}

-- Direction: SCF ® SSF, Timer: Tcon
-- This operation is used to request the SSF to perform the call processing actions to route or forward a call to
-- a specified destination. To do so, the SSF may or may not use destination information from the calling party
-- (e.g. dialled digits) and existing call set-up information (e.g. route index to a list of trunk groups), depending on
-- the information provided by the SCF.
-- – When address information is only included in the Connect operation, call processing resumes at PIC3 in
-- the O-BCSM.
-- – When address information and routing information is included, call processing resumes at PIC4.
ConnectArg ::= SEQUENCE {
destinationRoutingAddress [0] DestinationRoutingAddress, 
alertingPattern [1] AlertingPattern OPTIONAL,
correlationID [2] CorrelationID OPTIONAL,
cutAndPaste [3] CutAndPaste OPTIONAL,
forwardingCondition [4] ForwardingCondition OPTIONAL,
iSDNAccessRelatedInformation [5] ISDNAccessRelatedInformation OPTIONAL,
originalCalledPartyID [6] OriginalCalledPartyID OPTIONAL,
routeList [7] RouteList OPTIONAL,
scfID [8] ScfID OPTIONAL,
travellingClassMark [9] TravellingClassMark OPTIONAL,
extensions [10] SEQUENCE SIZE(1..numOfExtensions) OF
ExtensionField OPTIONAL,
carrier [11] Carrier OPTIONAL,
serviceInteractionIndicators [26] ServiceInteractionIndicators OPTIONAL,
callingPartyNumber [27] CallingPartyNumber OPTIONAL,
callingPartysCategory [28] CallingPartysCategory OPTIONAL,
redirectingPartyID [29] RedirectingPartyID OPTIONAL,
redirectionInformation [30] RedirectionInformation OPTIONAL,
displayInformation [12] DisplayInformation OPTIONAL,
forwardCallIndicators [13] ForwardCallIndicators OPTIONAL,
genericNumbers [14] GenericNumbers OPTIONAL,
serviceInteractionIndicatorsTwo [15] ServiceInteractionIndicatorsTwo OPTIONAL,
iNServiceCompatibilityResponse [16] INServiceCompatibilityResponse OPTIONAL,
forwardGVNS [17] ForwardGVNS OPTIONAL,
backwardGVNS [18] BackwardGVNS OPTIONAL,
chargeNumber [19] ChargeNumber OPTIONAL,
callSegmentID [20] CallSegmentID OPTIONAL,
legToBeCreated [21] LegID OPTIONAL
}
-- For alerting pattern, OPTIONAL denotes that this parameter only applies if SSF is the terminating local
-- exchange for the subscriber.
ConnectToResource ::= OPERATION
ARGUMENT ConnectToResourceArg 
-- RETURN RESULT FALSE
ERRORS {missingParameter ,
systemFailure ,
taskRefused ,
unexpectedComponentSequence ,
unexpectedDataValue ,
unexpectedParameter,
unknownLegID}

-- Direction: SCF ® SSF, Timer: Tctr
-- This operation is used to connect a call from the SSP to the physical entity containing the SRF.
-- Refer to clause 17 for a description of the procedures associated with this operation.
ConnectToResourceArg ::= SEQUENCE {
resourceAddress CHOICE {
ipRoutingAddress [0] IPRoutingAddress, 
legID [1] LegID,
ipAddressAndLegID [2] SEQUENCE {
ipRoutingAddress [0] IPRoutingAddress ,
legID [1] LegID
},
none [3] NULL,
callSegmentID [5] CallSegmentID ,
ipAddressAndCallSegment [6] SEQUENCE {
ipRoutingAddress [0] IPRoutingAddress ,
callSegmentID [1] CallSegmentID 
}
},
extensions [4] SEQUENCE SIZE(1..numOfExtensions) OF
ExtensionField OPTIONAL,
serviceInteractionIndicators [30] ServiceInteractionIndicators OPTIONAL,
serviceInteractionIndicatorsTwo [7] ServiceInteractionIndicatorsTwo OPTIONAL
}

Continue ::= OPERATION
-- RETURN RESULT FALSE
--ALWAYS RESPONDS FALSE

-- Direction: SCF ® SSF, Timer: Tcue
-- This operation is used to request the SSF to proceed with call processing at the DP at which it
-- previously suspended call processing to await SCF instructions (i.e. proceed to the next point
-- in call in the BCSM). The SSF continues call processing without substituting new data from SCF.
-- This operation is not valid for a single call segment CSA with more than 2 legs or a multi call segment CSA.
ContinueWithArgument ::= OPERATION
ARGUMENT ContinueWithArgumentArg 
-- RETURN RESULT FALSE
ERRORS {missingParameter ,
unexpectedComponentSequence ,
unexpectedParameter ,
unexpectedDataValue
}
--CODE opcode-continueWithArgument}
-- Direction: SCF ® SSF, Timer: Tcwa
-- This operation is used to request the SSF to proceed with call processing at the DP where it previously
-- suspended call processing to await SCF instructions.
-- It is also used to provide additional service related information to a User (Called Party or Calling Party) whilst
-- the call processing proceeds.
ContinueWithArgumentArg ::= SEQUENCE {
legID [0] LegID DEFAULT
sendingSideID:leg1,
alertingPattern [1] AlertingPattern OPTIONAL,
genericName [2] GenericName OPTIONAL,
iNServiceCompatibilityResponse [3] INServiceCompatibilityResponse OPTIONAL,
forwardGVNS [4] ForwardGVNS OPTIONAL,
backwardGVNS [5] BackwardGVNS OPTIONAL,
extensions [6] SEQUENCE SIZE (1..numOfExtensions) OF
ExtensionField OPTIONAL,
serviceInteractionIndicatorsTwo [7] ServiceInteractionIndicatorsTwo OPTIONAL
}

CreateCallSegmentAssociation ::= OPERATION
ARGUMENT CreateCallSegmentAssociationArg
RESULT CreateCallSegmentAssociationResult 
ERRORS {missingParameter ,
systemFailure,
taskRefused,
unexpectedComponentSequence,
unexpectedDataValue ,
unexpectedParameter
}

-- Direction: SCF ® SSF, Timer: Tcsa
-- This operation is used to create a new CSA. The new CSA will not contain any Call Segments after creation.
-- The SSF is responsible for specifying a new CSA identifier for the created CSA which is unique within
-- the SSF.
CreateCallSegmentAssociationArg ::= SEQUENCE {
extensions [0] SEQUENCE SIZE (1..numOfExtensions) OF
ExtensionField OPTIONAL
}
CreateCallSegmentAssociationResult ::= SEQUENCE {
newCallSegmentAssociation [0] CSAID 
}

DisconnectForwardConnection ::= OPERATION
-- RETURN RESULTFALSE FALSE
ERRORS {systemFailure ,
taskRefused ,
unexpectedComponentSequence }

-- Direction: SCF ® SSF, Timer: Tdfc
-- This operation is used to disconnect a forward temporary connection or a connection to a resource.
-- Refer to clause 17 for a description of the procedures associated with this operation.
-- This operation is not valid for a single call segment CSA with more than 2 legs or a multi call segment CSA.
DisconnectForwardConnectionWithArgument ::= OPERATION
ARGUMENT DisconnectForwardConnectionWithArgumentArg 
-- RETURN RESULT FALSE
ERRORS {missingParameter ,
systemFailure ,
taskRefused ,
unexpectedComponentSequence, 
unexpectedDataValue ,
unexpectedParameter ,
unknownLegID}

-- Direction: SCF ® SSF, Timer: Tdfcwa
-- This operation is used to disconnect a forward temporary connection or a connection to a resource.
-- Refer to clause 17 for a description of the procedures associated with this operation.
DisconnectForwardConnectionWithArgumentArg ::= SEQUENCE {
partyToDisconnect CHOICE {
legID [0] LegID,
callSegmentID [1] CallSegmentID 
},
extensions [2] SEQUENCE SIZE (1..numOfExtensions) OF
ExtensionField OPTIONAL
}

DisconnectLeg ::= OPERATION
ARGUMENT DisconnectLegArg 
-- RETURN RESULT TRUE
ERRORS {missingParameter,
systemFailure ,
taskRefused ,
unexpectedComponentSequence ,
unexpectedDataValue ,
unexpectedParameter,
unknownLegID}

-- Direction: SCF ® SSF, Timer: Tdl
-- This operation is issued by the SCF to release a specific leg associated with the call and retain any
-- other legs not specified in the DisconnectLeg. Any leg may be disconnected, including the controlling
-- leg, without completely releasing all legs.
-- For additional information on this operation, refer to Rec. Q.1224.

DisconnectLegArg ::= SEQUENCE {
legToBeReleased [0] LegID,
releaseCause [1] Cause OPTIONAL,
extensions [2] SEQUENCE SIZE (1..numOfExtensions) OF
ExtensionField OPTIONAL
}

EntityReleased ::= OPERATION
ARGUMENT EntityReleasedArg 
-- RETURN RESULT FALSE
--ALWAYS RESPONDS FALSE

-- Direction: SSF ® SCF, Timer: Ter
-- This operation is used by SSF to inform the SCF of an error/exception
EntityReleasedArg ::= CHOICE {
cSFailure [0] SEQUENCE{
	callSegmentID [0] CallSegmentID, 
	reason [1] Reason OPTIONAL,
	cause [2] Cause OPTIONAL 
	},
bCSMFailure [1] SEQUENCE{
	legID [0] LegID,
	reason [1] Reason OPTIONAL,
	cause [2] Cause OPTIONAL
	}
}

EstablishTemporaryConnection ::= OPERATION
ARGUMENT EstablishTemporaryConnectionArg 
-- RETURN RESULTFALSE FALSE
ERRORS {eTCFailed ,
missingParameter ,
systemFailure ,
taskRefused ,
unexpectedComponentSequence ,
unexpectedDataValue ,
unexpectedParameter,
unknownLegID}

-- Direction: SCF ® SSF, Timer: Tetc
-- This operation is used to create a connection to a resource for a limited period of time
-- (e.g. to play an announcement, to collect user information); it implies the use of the assist
-- procedure. Refer to clause 17 for a description of the procedures associated with this operation.

EstablishTemporaryConnectionArg ::= SEQUENCE {
assistingSSPIPRoutingAddress [0] AssistingSSPIPRoutingAddress ,
correlationID [1] CorrelationID OPTIONAL,
partyToConnect CHOICE {
legID [2] LegID,
callSegmentID [7] CallSegmentID 
} OPTIONAL,
scfID [3] ScfID OPTIONAL,
extensions [4] SEQUENCE SIZE(1..numOfExtensions)
OF ExtensionField OPTIONAL,
carrier [5] Carrier OPTIONAL,
serviceInteractionIndicators [30] ServiceInteractionIndicators OPTIONAL,
serviceInteractionIndicatorsTwo [6] ServiceInteractionIndicatorsTwo OPTIONAL
}

EventNotificationCharging ::= OPERATION
ARGUMENT EventNotificationChargingArg 
-- RETURN RESULT FALSE
--ALWAYS RESPONDS FALSE

-- Direction: SSF ® SCF, Timer: Tenc
-- This operation is used by the SSF to report to the SCF the occurrence of a specific charging event
-- type as previously requested by the SCF in a RequestNotificationChargingEvent operation.
EventNotificationChargingArg ::= SEQUENCE {
eventTypeCharging [0] EventTypeCharging, 
eventSpecificInformationCharging [1] EventSpecificInformationCharging OPTIONAL,
legID [2] LegID OPTIONAL,
extensions [3] SEQUENCE SIZE(1..numOfExtensions) OF
ExtensionField OPTIONAL,
monitorMode [30] MonitorMode DEFAULT notifyAndContinue
}
-- OPTIONAL denotes network-operator specific use.
EventReportBCSM ::= OPERATION
ARGUMENT EventReportBCSMArg 
-- RETURN RESULT FALSE
--ALWAYS RESPONDS FALSE

-- Direction: SSF ® SCF, Timer: Terb
-- This operation is used to notify the SCF of a call-related event (e.g. BCSM events such as busy or
-- no answer) previously requested by the SCF in a RequestReportBCSMEvent operation.
EventReportBCSMArg ::= SEQUENCE {
eventTypeBCSM [0] EventTypeBCSM,
bcsmEventCorrelationID [1] CorrelationID OPTIONAL,
eventSpecificInformationBCSM [2] EventSpecificInformationBCSM OPTIONAL,
legID [3] LegID OPTIONAL,
miscCallInfo [4] MiscCallInfo DEFAULT {messageType request},
extensions [5] SEQUENCE SIZE(1..numOfExtensions) OF
ExtensionField OPTIONAL,
componentType [6] ComponentType OPTIONAL,
component [7] Component OPTIONAL,
componentCorrelationID [8] ComponentCorrelationID OPTIONAL
}

EventReportFacility ::= OPERATION
ARGUMENT EventReportFacilityArg 
-- RETURN RESULT FALSE
--ALWAYS RESPONDS FALSE

-- Direction: SSF ® SCF, Timer: Terf
-- This operation is issued by the SSF to report the event to the SCF, that was previously requested by the
-- SCF, the CCF/SSF receives a DSS 1 message which contains a FACILITY IE. Criteria for the report, like
-- reception of the ReturnResult which is specified with ComponentType, is optionally checked
-- before issuing this operation.
EventReportFacilityArg ::= SEQUENCE{
componentType [0] ComponentType OPTIONAL,
component [1] Component OPTIONAL,
legID [2] LegID OPTIONAL,
componentCorrelationID [3] ComponentCorrelationID OPTIONAL,
extensions [4] SEQUENCE SIZE(1..numOfExtensions) OF
ExtensionField OPTIONAL
}
-- When the monitorDuration is over and the report condition specified with RequestReportFacilityEvent
-- was not met, component shall be absent.
FacilitySelectedAndAvailable ::= OPERATION
ARGUMENT FacilitySelectedAndAvailableArg 
-- RETURN RESULT FALSE
ERRORS {missingCustomerRecord ,
missingParameter ,
systemFailure ,
taskRefused ,
unexpectedComponentSequence ,
unexpectedDataValue ,
unexpectedParameter}

-- Direction: SSF ® SCF, Timer: Tfs
-- This operation is used for indication of a call termination attempt from the terminating half BCSM. (DP –
-- Facility_Selected_And_Available).
-- For additional information on this operation, refer to Rec. Q.1224.
FacilitySelectedAndAvailableArg ::= SEQUENCE {
dpSpecificCommonParameters [0] DpSpecificCommonParameters, 
calledPartyBusinessGroupID [1] CalledPartyBusinessGroupID OPTIONAL,
calledPartySubaddress [2] CalledPartySubaddress OPTIONAL,
callingPartyBusinessGroupID [3] CallingPartyBusinessGroupID OPTIONAL,
callingPartyNumber [4] CallingPartyNumber OPTIONAL,
originalCalledPartyID [5] OriginalCalledPartyID OPTIONAL,
redirectingPartyID [6] RedirectingPartyID OPTIONAL,
redirectionInformation [7] RedirectionInformation OPTIONAL,
routeList [8] RouteList OPTIONAL,
travellingClassMark [9] TravellingClassMark OPTIONAL,
extensions [10] SEQUENCE SIZE(1..numOfExtensions) OF
ExtensionField OPTIONAL,
componentType [11] ComponentType OPTIONAL,
component [12] Component OPTIONAL,
componentCorrelationID [13] ComponentCorrelationID OPTIONAL
}
-- For the OPTIONAL parameters, refer to clause 17 for the trigger detection point processing rules
-- to specify when these parameters are included in the message.
FurnishChargingInformation ::= OPERATION
ARGUMENT FurnishChargingInformationArg 
-- RETURN RESULT FALSE
ERRORS {missingParameter ,
taskRefused ,
unexpectedComponentSequence ,
unexpectedDataValue ,
unexpectedParameter}

-- Direction: SCF ® SSF, Timer: Tfci
-- This operation is used to request the SSF to generate, register a call record or to include some information
-- in the default call record. The registered call record is intended for off-line charging of the call.
FurnishChargingInformationArg ::= FCIBillingChargingCharacteristics

HoldCallInNetwork ::= OPERATION
ARGUMENT HoldCallInNetworkArg
-- RETURN RESULT FALSE
ERRORS {missingParameter ,
systemFailure ,
taskRefused ,
unexpectedComponentSequence ,
unexpectedDataValue ,
unexpectedParameter}

-- Direction: SCF ® SSF, Timer: Thcn
-- This operation is used to provide the capability of queueing a call during the set-up phase (e.g. to provide
-- a call completion to busy, the call would be queued until the destination becomes free).
FurnishChargingInformationArg ::= FCIBillingChargingCharacteristics

HoldCallInNetwork ::= OPERATION
ARGUMENT HoldCallInNetworkArg
-- RETURN RESULT FALSE
ERRORS {missingParameter ,
systemFailure ,
taskRefused ,
unexpectedComponentSequence ,
unexpectedDataValue ,
unexpectedParameter}

-- holdcause is optional and denotes network-operator specific use.
InitialDP ::= OPERATION
ARGUMENT InitialDPArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Tidp
-- This operation is used after a TDP to indicate request for service.
InitialDPArg ::= SEQUENCE {
serviceKey [0] ServiceKey OPTIONAL,
dialledDigits [1] CalledPartyNumber OPTIONAL,
calledPartyNumber [2] CalledPartyNumber OPTIONAL,
callingPartyNumber [3] CallingPartyNumber OPTIONAL,
callingPartyBusinessGroupID [4] CallingPartyBusinessGroupID OPTIONAL,
callingPartysCategory [5] CallingPartysCategory OPTIONAL,
callingPartySubaddress [6] CallingPartySubaddress OPTIONAL,
cGEncountered [7] CGEncountered OPTIONAL,
iPSSPCapabilities [8] IPSSPCapabilities OPTIONAL,
iPAvailable [9] IPAvailable OPTIONAL,
locationNumber [10] LocationNumber OPTIONAL,
miscCallInfo [11] MiscCallInfo OPTIONAL,
originalCalledPartyID [12] OriginalCalledPartyID OPTIONAL,
serviceProfileIdentifier [13] ServiceProfileIdentifier OPTIONAL,
terminalType [14] TerminalType OPTIONAL,
extensions [15] SEQUENCE SIZE(1..numOfExtensions) OF
ExtensionField OPTIONAL,
triggerType [16] TriggerType OPTIONAL,
highLayerCompatibility [23] HighLayerCompatibility OPTIONAL,
serviceInteractionIndicators [24] ServiceInteractionIndicators OPTIONAL,
additionalCallingPartyNumber [25] AdditionalCallingPartyNumber OPTIONAL,
forwardCallIndicators [26] ForwardCallIndicators OPTIONAL,
bearerCapability [27] BearerCapability OPTIONAL,
eventTypeBCSM [28] EventTypeBCSM OPTIONAL,
redirectingPartyID [29] RedirectingPartyID OPTIONAL,
redirectionInformation [30] RedirectionInformation OPTIONAL,
cause [17] Cause OPTIONAL,
componentType [18] ComponentType OPTIONAL,
component [19] Component OPTIONAL,
componentCorrelationID [20] ComponentCorrelationID OPTIONAL,
iSDNAccessRelatedInformation [21] ISDNAccessRelatedInformation OPTIONAL,
iNServiceCompatibilityIndication [22] INServiceCompatibilityIndication OPTIONAL,
genericNumbers [31] GenericNumbers OPTIONAL,
serviceInteractionIndicatorsTwo [32] ServiceInteractionIndicatorsTwo OPTIONAL,
forwardGVNS [33] ForwardGVNS OPTIONAL,
createdCallSegmentAssociation [34] CSAID OPTIONAL,
uSIServiceIndicator [35] USIServiceIndicator OPTIONAL,
uSIInformation [36] USIInformation OPTIONAL
}

-- OPTIONAL for iPSSPCapabilities, iPAvailable, cGEncountered, and miscCallInfo denotes network-
-- operator specific use.
-- OPTIONAL for dialledDigits, callingPartyNumber, and callingPartysCategory refer to clause 17 for the trigger
-- detection point processing rules to specify when these parameters are included in the message.
-- OPTIONAL for terminalType indicates that this parameter applies only at originating or terminating
-- local exchanges if the SSF has this information.
InitiateCallAttempt ::= OPERATION
ARGUMENT InitiateCallAttemptArg 
-- RETURN RESULT FALSE
ERRORS {missingParameter ,
parameterOutOfRange ,
systemFailure ,
taskRefused ,
unexpectedComponentSequence ,
unexpectedDataValue ,
unexpectedParameter,
unknownLegID
}

-- Direction: SCF ® SSF, Timer: Tica
-- This operation is used to request the SSF to create a new call to one call party using address
-- information provided by the SCF.
InitiateCallAttemptArg ::= SEQUENCE {
destinationRoutingAddress [0] DestinationRoutingAddress, 
alertingPattern [1] AlertingPattern OPTIONAL,
iSDNAccessRelatedInformation [2] ISDNAccessRelatedInformation OPTIONAL,
travellingClassMark [3] TravellingClassMark OPTIONAL,
extensions [4] SEQUENCE SIZE(1..numOfExtensions) OF
ExtensionField OPTIONAL,
serviceInteractionIndicators [29] ServiceInteractionIndicators OPTIONAL,
callingPartyNumber [30] CallingPartyNumber OPTIONAL,
legToBeCreated [5] LegID DEFAULT sendingSideID:leg1,
newCallSegment [6] CallSegmentID DEFAULT initialCallSegment,
iNServiceCompatibilityResponse [7] INServiceCompatibilityResponse OPTIONAL,
serviceInteractionIndicatorsTwo [8] ServiceInteractionIndicatorsTwo OPTIONAL
}
ManageTriggerData ::= OPERATION
ARGUMENT ManageTriggerDataArg 
RESULT ManageTriggerDataResultArg 
ERRORS {missingParameter ,
parameterOutOfRange ,
systemFailure ,
taskRefused ,
unexpectedComponentSequence ,
unexpectedDataValue ,
unexpectedParameter
}

-- Direction: SCF ® SSF, Class 1, Timer: Tmtd
-- This operation is used to activate, deactivate or retrieve
-- the status of a trigger detection point linked to a subscriber profile known at the switch, e.g. related to an access line.

ManageTriggerDataArg ::= SEQUENCE {
actionIndicator [0] ActionIndicator,
triggerDataIdentifier [1] TriggerDataIdentifier ,
registratorIdentifier [2] RegistratorIdentifier OPTIONAL,
extensions [3] SEQUENCE SIZE (1..numOfExtensions) OF
ExtensionField OPTIONAL
}
ManageTriggerDataResultArg ::= SEQUENCE {
actionPerformed [0] ActionPerformed,
extensions [1] SEQUENCE SIZE (1..numOfExtensions) OF
ExtensionField OPTIONAL
}

MergeCallSegments ::= OPERATION
ARGUMENT MergeCallSegmentsArg 
-- RETURN RESULT TRUE
ERRORS {missingParameter ,
systemFailure ,
taskRefused ,
unexpectedComponentSequence ,
unexpectedDataValue ,
unexpectedParameter
}

-- Direction: SCF ® SSF, Timer: Tmc
-- This operation is issued by the SCF to merge two associated CSs with a single controlling leg into one
-- CS with that controlling leg.
-- For additional information on this operation, refer to Rec. Q.1224.
MergeCallSegmentsArg ::= SEQUENCE {
sourceCallSegment [0] CallSegmentID ,
targetCallSegment [1] CallSegmentID DEFAULT initialCallSegment,
extensions [2] SEQUENCE SIZE (1..numOfExtensions)
OF ExtensionField OPTIONAL
}

MoveCallSegments ::= OPERATION
ARGUMENT MoveCallSegmentsArg 
-- RETURN RESULT TRUE
ERRORS {missingParameter ,
systemFailure ,
taskRefused ,
unexpectedComponentSequence ,
unexpectedDataValue ,
unexpectedParameter,
unknownLegID
}

-- Direction: SCF ® SSF, Timer Tmcs
-- This operation is used to merge two call segments into one.

MoveCallSegmentsArg ::= SEQUENCE {
targetCallSegmentAssociation [0] CSAID ,
-- assignement of CSAID by SSF/SCF is ffs.
callSegments [1] SEQUENCE SIZE (1..numOfCSs) OF SEQUENCE {
sourceCallSegment [0] CallSegmentID DEFAULT initialCallSegment,
newCallSegment [1] CallSegmentID 
},
legs [2] SEQUENCE SIZE (1..numOfLegs) OF SEQUENCE {
sourceLeg [0] LegID,
newLeg [1] LegID
},
extensions [2] SEQUENCE SIZE (1..numOfExtensions)
OF ExtensionField OPTIONAL
}

MoveLeg ::= OPERATION
ARGUMENT MoveLegArg 
-- RETURN RESULT TRUE
ERRORS {missingParameter ,
systemFailure ,
taskRefused ,
unexpectedComponentSequence ,
unexpectedDataValue ,
unexpectedParameter,
unknownLegID
}

-- Direction : SCF ® SSF, Timer: Tml
-- This operation is issued by the SCF to move a leg from one CS to another with which it is associated.
MoveLegArg ::= SEQUENCE {
legIDToMove [0] LegID,
targetCallSegment [1] CallSegmentID DEFAULT 1,
extensions [2] SEQUENCE SIZE (1..numOfExtensions) OF
ExtensionField OPTIONAL
}
-- For the OPTIONAL parameters, refer to clause 17 for the trigger
-- detection point processing rules to specify when these parameters are
-- included in the message.
OAbandon ::= OPERATION
ARGUMENT OAbandonArg 
-- RETURN RESULT FALSE
ERRORS {missingCustomerRecord ,
missingParameter ,
systemFailure ,
taskRefused ,
unexpectedComponentSequence ,
unexpectedDataValue ,
unexpectedParameter ,
unknownLegID
}


-- Direction: SSF ® SCF, Timer: Tob
-- This operation is issued by the SSF after detecting a valid trigger condition at the O_Abandon DP or to
-- report an oAbandon event requested by the RequestReportBCSMEvent. For additional information on this
-- operation, refer to Rec. Q.1224.
OAbandonArg ::= SEQUENCE {
dpSpecificCommonParameters [0] DpSpecificCommonParameters, 
callSegmentID [1] CallSegmentID ,
releaseCause [2] Cause OPTIONAL,
extensions [3] SEQUENCE SIZE(1..numOfExtensions)OF
ExtensionField OPTIONAL
}
-- For the OPTIONAL parameters, refer to clause 17 for the trigger detection point rules to specify
-- when these parameters are included in the message.
-- Type definition for PointInCall is ffs. Use of T/EDP-R is ffs.
OAnswer ::= OPERATION
ARGUMENT OAnswerArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Toa
-- This operation is used for indication from the terminating half BCSM that the call is accepted and answered
-- by terminating party (e.g. terminating party goes off-hook, Q.931 Connect message received, ISDN-UP Answer
-- message received) (DP – O_Answer). For additional information on this operation, refer to Rec. Q.1224.
OAnswerArg ::= SEQUENCE {
dpSpecificCommonParameters [0] DpSpecificCommonParameters ,
callingPartyBusinessGroupID [1] CallingPartyBusinessGroupID OPTIONAL,
callingPartySubaddress [2] CallingPartySubaddress OPTIONAL,
callingFacilityGroup [3] FacilityGroup OPTIONAL,
callingFacilityGroupMember [4] FacilityGroupMember OPTIONAL,
originalCalledPartyID [5] OriginalCalledPartyID OPTIONAL,
redirectingPartyID [6] RedirectingPartyID OPTIONAL,
redirectionInformation [7] RedirectionInformation OPTIONAL,
routeList [8] RouteList OPTIONAL,
travellingClassMark [9] TravellingClassMark OPTIONAL,
extensions [10] SEQUENCE SIZE(1..numOfExtensions) OF
ExtensionField OPTIONAL
}
-- For the OPTIONAL parameters, refer to clause 17 for the trigger detection point processing rules
-- to specify when these parameters are included in the message.
OCalledPartyBusy ::= OPERATION
ARGUMENT OCalledPartyBusyArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Tob
-- This operation is used for Indication from the terminating half BCSM that the terminating party is busy
-- (DP – O_Called_Party_Busy). For additional information on this operation, refer to Rec. Q.1224.
OCalledPartyBusyArg ::= SEQUENCE {
dpSpecificCommonParameters [0] DpSpecificCommonParameters, 
busyCause [1] Cause OPTIONAL,
callingPartyBusinessGroupID [2] CallingPartyBusinessGroupID OPTIONAL,
callingPartySubaddress [3] CallingPartySubaddress OPTIONAL,
callingFacilityGroup [4] FacilityGroup OPTIONAL,
callingFacilityGroupMember [5] FacilityGroupMember OPTIONAL,
originalCalledPartyID [6] OriginalCalledPartyID OPTIONAL,
prefix [7] Digits OPTIONAL,
redirectingPartyID [8] RedirectingPartyID OPTIONAL,
redirectionInformation [9] RedirectionInformation OPTIONAL,
routeList [10] RouteList OPTIONAL,
travellingClassMark [11] TravellingClassMark OPTIONAL,
extensions [12] SEQUENCE SIZE(1..numOfExtensions) OF
ExtensionField OPTIONAL,
carrier [13] Carrier OPTIONAL
}
-- For the OPTIONAL parameters, refer to clause 17 for the trigger detection point processing rules
-- to specify when these parameters are included in the message.
ODisconnect ::= OPERATION
ARGUMENT ODisconnectArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Tod
-- This operation is used for a disconnect indication (e.g. on-hook, Q.931 Disconnect message, SS7 Release message)
-- is received from the originating party, or received from the terminating party via the terminating half BCSM.
-- (DP – O_Disconnect). For additional information on this operation, refer to Rec.Q.1224.

ODisconnectArg ::= SEQUENCE {
dpSpecificCommonParameters [0] DpSpecificCommonParameters, 
callingPartyBusinessGroupID [1] CallingPartyBusinessGroupID OPTIONAL,
callingPartySubaddress [2] CallingPartySubaddress OPTIONAL,
callingFacilityGroup [3] FacilityGroup OPTIONAL,
callingFacilityGroupMember [4] FacilityGroupMember OPTIONAL,
releaseCause [5] Cause OPTIONAL,
routeList [6] RouteList OPTIONAL,
extensions [7] SEQUENCE SIZE(1..numOfExtensions)OF
ExtensionField OPTIONAL,
carrier [8] Carrier OPTIONAL,
connectTime [9] Integer4 OPTIONAL,
componentType [10] ComponentType OPTIONAL,
component [11] Component OPTIONAL,
componentCorrelationID [12] ComponentCorrelationID OPTIONAL
}
-- For the OPTIONAL parameters, refer to clause 17 for the trigger detection point processing rules
-- to specify when these parameters are included in the message.
OMidCall ::= OPERATION
ARGUMENT MidCallArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Tomc
-- This operation is used to indicate a feature request is received from the originating party
-- (e.g. hook flash, ISDN feature activation, Q.931 HOLD or RETrieve message). (DP – O_Mid_Call).
-- For additional information on this operation, refer to Rec. Q.1224.
MidCallArg ::= SEQUENCE {
dpSpecificCommonParameters [0] DpSpecificCommonParameters ,
calledPartyBusinessGroupID [1] CalledPartyBusinessGroupID OPTIONAL,
calledPartySubaddress [2] CalledPartySubaddress OPTIONAL,
callingPartyBusinessGroupID [3] CallingPartyBusinessGroupID OPTIONAL,
callingPartySubaddress [4] CallingPartySubaddress OPTIONAL,
featureRequestIndicator [5] FeatureRequestIndicator OPTIONAL,
extensions [6] SEQUENCE SIZE(1..numOfExtensions)OF
ExtensionField OPTIONAL,
carrier [7] Carrier OPTIONAL,
componentType [8] ComponentType OPTIONAL,
component [9] Component OPTIONAL,
componentCorrelationID [10] ComponentCorrelationID OPTIONAL
}
-- For the OPTIONAL parameters, refer to clause 17 for the trigger detection point processing rules
-- to specify when these parameters are included in the message.

ONoAnswer ::= OPERATION
ARGUMENT ONoAnswerArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Tona
-- This operation is used for indication from the terminating half BCSM that the terminating party does not
-- answer within a specified time period (DP – O_No_Answer). For additional information on this operation,
-- refer to Rec. Q.1224.
ONoAnswerArg ::= SEQUENCE {
dpSpecificCommonParameters [0] DpSpecificCommonParameters ,
callingPartyBusinessGroupID [1] CallingPartyBusinessGroupID OPTIONAL,
callingPartySubaddress [2] CallingPartySubaddress OPTIONAL,
callingFacilityGroup [3] FacilityGroup OPTIONAL,
callingFacilityGroupMember [4] FacilityGroupMember OPTIONAL,
originalCalledPartyID [5] OriginalCalledPartyID OPTIONAL,
prefix [6] Digits OPTIONAL,
redirectingPartyID [7] RedirectingPartyID OPTIONAL,
redirectionInformation [8] RedirectionInformation OPTIONAL,
routeList [9] RouteList OPTIONAL,
travellingClassMark [10] TravellingClassMark OPTIONAL,
extensions [11] SEQUENCE SIZE(1..numOfExtensions) OF
ExtensionField OPTIONAL,
carrier [12] Carrier OPTIONAL
}
-- For the OPTIONAL parameters, refer to clause 17 for the trigger detection point processing rules
-- to specify when these parameters are included in the message.
OriginationAttempt ::= OPERATION
ARGUMENT OriginationAttemptArg 
-- RETURN RESULT FALSE
ERRORS {missingCustomerRecord ,
missingParameter ,
systemFailure ,
taskRefused ,
unexpectedComponentSequence ,
unexpectedDataValue ,
unexpectedParameter
}

-- Direction: SSF ® SCF, Timer: Tora
-- This operation is used for indication of a call origination attempt from the originating half BCSM. (DP –
-- Origination_Attempt).
-- For additional information on this operation, refer to Rec. Q.1224.

OriginationAttemptArg ::= SEQUENCE {
dpSpecificCommonParameters [0] DpSpecificCommonParameters, 
callingPartyBusinessGroupID [1] CallingPartyBusinessGroupID OPTIONAL,
callingPartySubaddress [2] CallingPartySubaddress OPTIONAL,
callingFacilityGroup [3] FacilityGroup OPTIONAL,
callingFacilityGroupMember [4] FacilityGroupMember OPTIONAL,
carrier [5] Carrier OPTIONAL,
travellingClassMark [6] TravellingClassMark OPTIONAL,
extensions [7] SEQUENCE SIZE(1..numOfExtensions)OF
ExtensionField OPTIONAL,
componentType [8] ComponentType OPTIONAL,
component [9] Component OPTIONAL,
componenttCorrelationID [10] ComponentCorrelationID OPTIONAL
}
-- For the OPTIONAL parameters, refer to clause 17 for the trigger detection point processing rules
-- to specify when these parameters are included in the message.
OriginationAttemptAuthorized ::= OPERATION
ARGUMENT OriginationAttemptAuthorizedArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Toaa
-- This operation is used to Indicate the desire to place outgoing call (e.g. off-hook, Q.931 Setup message,
-- ISDN-UP IAM message) and authority/ability to place outgoing call verified (DP –
-- Origination_Attempt_Authorized).
-- For additional information on this operation, refer to Rec. Q.1224.
OriginationAttemptAuthorizedArg ::= SEQUENCE {
dpSpecificCommonParameters [0] DpSpecificCommonParameters, 
dialledDigits [1] CalledPartyNumber OPTIONAL,
callingPartyBusinessGroupID [2] CallingPartyBusinessGroupID OPTIONAL,
callingPartySubaddress [3] CallingPartySubaddress OPTIONAL,
callingFacilityGroup [4] FacilityGroup OPTIONAL,
callingFacilityGroupMember [5] FacilityGroupMember OPTIONAL,
travellingClassMark [6] TravellingClassMark OPTIONAL,
extensions [7] SEQUENCE SIZE(1..numOfExtensions)OF
ExtensionField OPTIONAL,
carrier [8] Carrier OPTIONAL,
componentType [9] ComponentType OPTIONAL,
component [10] Component OPTIONAL,
componentCorrelationID [11] ComponentCorrelationID OPTIONAL

}
-- For the OPTIONAL parameters, refer to clause 17 for the trigger detection point processing rules
-- to specify when these parameters are included in the message.

OSuspended ::= OPERATION
ARGUMENT OSuspendedArg 
-- RETURN RESULT FALSE
ERRORS {missingCustomerRecord ,
missingParameter ,
systemFailure ,
taskRefused ,
unexpectedComponentSequence ,
unexpectedDataValue ,
unexpectedParameter ,
unknownLegID
}

-- Direction: SSF ® SCF, Timer: Tos
-- This operation is issued by the SSF after detecting a valid trigger condition at the O_Suspended DP or to
-- report an oSuspended event requested by the RequestReportBCSMEvent. For additional information on
-- this operation, refer to Rec. Q.1224.
OSuspendedArg ::= SEQUENCE {
dpSpecificCommonParameters [0] DpSpecificCommonParameters, 
legID [1] LegID OPTIONAL,
extensions [2] SEQUENCE SIZE(1..numOfExtensions)OF
ExtensionField OPTIONAL

}
-- For the OPTIONAL parameters, refer to clause 17 for the trigger detection point processing rules
-- to specify when these parameters are included in the message.
-- Modification to LegID is ffs. Use for T/EDP-R is ffs.
Reconnect ::= OPERATION
ARGUMENT ReconnectArg 
-- RETURN RESULT FALSE
ERRORS {missingParameter ,
systemFailure ,
taskRefused ,
unexpectedComponentSequence ,
unexpectedDataValue ,
unexpectedParameter
}

-- Direction: SCF ® SSF, Timer: Tre
-- This operation is issued by the SCF to reestablish communication between the controlling leg and the
-- (held) passive leg(s). For additional information on this operation, refer to Rec. Q.1224.
ReconnectArg ::= SEQUENCE {
notificationDuration [0] ApplicationTimer OPTIONAL,
alertingPattern [1] AlertingPattern OPTIONAL,
displayInformation [2] DisplayInformation OPTIONAL,
extensions [3] SEQUENCE SIZE(1..numOfExtensions)OF
ExtensionField OPTIONAL,
callSegmentID [4] CallSegmentID OPTIONAL
}

-- For the OPTIONAL parameters, refer to clause 17 for the trigger detection point processing rules
-- to specify when these parameters are included in the message.
ReleaseCall ::= OPERATION
ARGUMENT ReleaseCallArg 
-- RETURN RESULT FALSE
--ALWAYS RESPONDS FALSE

-- Direction: SCF ® SSF, Timer: Trc
-- This operation is used to tear down an existing call at any phase of the call for all parties
-- involved in the call.
ReleaseCallArg ::= CHOICE {
initialCallSegment Cause, 
associatedCallSegment [1] SEQUENCE {
callSegment [0] INTEGER (2..numOfCSs),
releaseCause [1] Cause OPTIONAL
},
allCallSegments [2] SEQUENCE {
releaseCause [0] Cause OPTIONAL
}
}
-- A default value of decimal 31 (normal unspecified) should be coded appropriately.
ReportUTSI ::= OPERATION
ARGUMENT ReportUTSIArg 
-- RETURN RESULT FALSE
--ALWAYS RESPONDS FALSE

-- Direction: SSF ® SCF, Timer: Tru
-- This operation is issued by the SSF in the context of the USI feature. It is used to report the receipt
-- of a User to Service Information (UTSI) IE to the SCF.
ReportUTSIArg ::= SEQUENCE {
uSIServiceIndicator [0] USIServiceIndicator, 
legID [1] LegID DEFAULT receivingSideID:leg1,
uSIInformation [2] USIInformation ,
extensions [3] SEQUENCE SIZE(1..numOfExtensions) OF
ExtensionField OPTIONAL
}

RequestCurrentStatusReport ::= OPERATION
ARGUMENT RequestCurrentStatusReportArg 
RESULT RequestCurrentStatusReportResultArg 
ERRORS {missingParameter ,
parameterOutOfRange ,
systemFailure ,
taskRefused ,
unexpectedComponentSequence ,
unexpectedDataValue ,
unexpectedParameter,
unknownResource
}

-- Direction: SCF ® SSF, Timer: Trcs
-- This operation is used to request the SSF to report immediately the busy/idle status of a physical
-- termination resource.
RequestCurrentStatusReportArg ::= ResourceID 
RequestCurrentStatusReportResultArg ::= SEQUENCE {
resourceStatus [0] ResourceStatus,
resourceID [1] ResourceID OPTIONAL,
extensions [2] SEQUENCE SIZE(1..numOfExtensions)OF
ExtensionField OPTIONAL
}

RequestEveryStatusChangeReport ::= OPERATION
ARGUMENT RequestEveryStatusChangeReportArg 
-- RETURN RESULT TRUE
ERRORS {missingParameter ,
parameterOutOfRange ,
systemFailure ,
taskRefused ,
unexpectedComponentSequence ,
unexpectedDataValue ,
unexpectedParameter,
unknownResource
}

-- Direction: SCF ® SSF, Timer: Tres
-- This operation is used to request the SSF to report every change of busy/idle status of a physical
-- termination resource.
RequestEveryStatusChangeReportArg ::= SEQUENCE {
resourceID [0] ResourceID, 
correlationID [1] CorrelationID OPTIONAL,
monitorDuration [2] Duration OPTIONAL,
extensions [3] SEQUENCE SIZE(1..numOfExtensions)OF
ExtensionField OPTIONAL
}
-- For correlationID OPTIONAL denotes network-operator optional.
-- monitorDuration is required if outside the context of a call. It is not expected if we are in the context
-- of a call, because in that case the end of the call implicitly means the end of the monitoring.
RequestFirstStatusMatchReport ::= OPERATION
ARGUMENT RequestFirstStatusMatchReportArg
-- RETURN RESULT TRUE
ERRORS {missingParameter ,
parameterOutOfRange ,
systemFailure ,
taskRefused ,
unexpectedComponentSequence ,
unexpectedDataValue ,
unexpectedParameter,
unknownResource
}

-- Direction: SCF ® SSF, Timer: Trfs
-- This operation is used to request the SSF to report the first change busy/idle to the specified status of
-- a physical termination resource.
RequestFirstStatusMatchReportArg ::= SEQUENCE {
resourceID [0] ResourceID OPTIONAL,
resourceStatus [1] ResourceStatus OPTIONAL,
correlationID [2] CorrelationID OPTIONAL,
monitorDuration [3] Duration OPTIONAL,
extensions [4] SEQUENCE SIZE(1..numOfExtensions) OF
ExtensionField OPTIONAL,
bearerCapability [5] BearerCapability OPTIONAL
}
-- For correlationID OPTIONAL denotes network-operator optional.
-- monitorDuration is required if outside the context of a call. It is not expected if we are in the context
-- of a call, because in that case the end of the call implicitly means the end of the monitoring.
RequestNotificationChargingEvent ::= OPERATION
ARGUMENT RequestNotificationChargingEventArg 
-- RETURN RESULT FALSE
ERRORS {missingParameter ,
parameterOutOfRange ,
systemFailure ,
taskRefused ,
unexpectedComponentSequence ,
unexpectedDataValue ,
unexpectedParameter
}

-- Direction: SCF ® SSF, Timer: Trnc
-- This operation is used by the SCF to instruct the SSF on how to manage the charging events
-- which are received from other FEs and not under control of the service logic instance.
RequestNotificationChargingEventArg ::= SEQUENCE
SIZE(1..numOfChargingEvents) OF
ChargingEvent 

RequestReportBCSMEvent ::= OPERATION
ARGUMENT RequestReportBCSMEventArg 
-- RETURN RESULT FALSE
ERRORS {missingParameter ,
parameterOutOfRange ,
systemFailure ,
taskRefused ,
unexpectedComponentSequence ,
unexpectedDataValue ,
unexpectedParameter
}

-- Direction: SCF ® SSF, Timer: Trrb
-- This operation is used to request the SSF to monitor for a call-related event (e.g. BCSM events such as
-- busy or no answer), then send a notification back to the SCF when the event is detected.
-- It is proposed that Event Detection Point (EDP) processing is always initiated by RequestReportBCSMEvent and the
-- EDP may be acknowledged with either an EventReportBCSM or by a DP-specific operations:
-- NOTE –The application context should identify whether BCSM Event Handling Package
-- is being used, or whether DP Specific Event Handling Package
-- is being used.
-- – for a particular IN, only one of the two alternatives identified by the respective Packages should be
-- selected (i.e. only one approach should be selected for a given application context).
-- – Every EDP must be explicitly armed by the SCF via a RequestReportBCSMEvent operation. No
-- implicit arming of EDPs at the SSF after reception of any operation (different from
-- RequestReportBCSMEvent) from the SCF is allowed.
RequestReportBCSMEventArg ::= SEQUENCE {
bcsmEvents [0] SEQUENCE SIZE(1..numOfBCSMEvents) OF
BCSMEvent ,
bcsmEventCorrelationID [1] CorrelationID OPTIONAL,
extensions [2] SEQUENCE SIZE(1..numOfExtensions)OF
ExtensionField OPTIONAL
}
-- Indicates the BCSM related events for notification.
-- For correlationID OPTIONAL denotes network-operator optional.
RequestReportFacilityEvent ::= OPERATION
ARGUMENT RequestReportFacilityEventArg 
-- RETURN RESULT FALSE
ERRORS {missingParameter ,
systemFailure ,
taskRefused ,
unexpectedComponentSequence ,
unexpectedDataValue ,
unexpectedParameter ,
unknownLegID
}

-- Direction: SCF ® SSF, Timer: Trrfe
-- This operation is issued by the SCF to request the SSF to report the SCF the event that the CCF/SSF
-- receives a DSS 1 message which contains a FACILITY IE during a BCSM being suspended at a DP.
RequestReportFacilityEventArg ::= SEQUENCE{
componentTypes [0] SEQUENCE SIZE(1..3) OF ComponentType DEFAULT {any},
legID [1] LegID OPTIONAL,
componentCorrelationID [2] ComponentCorrelationID OPTIONAL,
monitorDuration [3] Duration,
extensions [4] SEQUENCE SIZE(1..numOfExtensions)OF
ExtensionField OPTIONAL
}
-- componentTypes specifies the component types which should be reported to the SCF.
-- monitorDuration specifies the monitor duration.
RequestReportUTSI ::= OPERATION
ARGUMENT RequestReportUTSIArg 
-- RETURN RESULT FALSE
ERRORS {missingParameter ,
systemFailure ,
taskRefused ,
unexpectedComponentSequence ,
unexpectedDataValue ,
unexpectedParameter
}

-- Direction: SCF ® SSF, Timer: Trru
-- This operation is issued by the SCF in the context of the USI feature to request the SSF to monitor for
-- a User to Service Information (UTSI) information element, which are received from a user.
RequestReportUTSIArg ::= SEQUENCE {
requestedUTSIList [0] RequestedUTSIList, 
extensions [1] SEQUENCE SIZE(1..numOfExtensions) OF
ExtensionField OPTIONAL,
legID [2] LegID OPTIONAL
}

ResetTimer ::= OPERATION
ARGUMENT ResetTimerArg 
-- RETURN RESULT FALSE
ERRORS {missingParameter ,
parameterOutOfRange ,
taskRefused ,
unexpectedComponentSequence ,
unexpectedDataValue ,
unexpectedParameter
}

-- Direction: SCF ® SSF, Timer: Trt
-- This operation is used to request the SSF to refresh an application timer in the SSF.
ResetTimerArg ::= SEQUENCE {
timerID [0] TimerID DEFAULT tssf,
timervalue [1] TimerValue,
extensions [2] SEQUENCE SIZE(1..numOfExtensions) OF
ExtensionField OPTIONAL,
callSegmentID [3] CallSegmentID OPTIONAL
}

RouteSelectFailure ::= OPERATION
ARGUMENT RouteSelectFailureArg 
-- RETURN RESULT FALSE
ERRORS {missingCustomerRecord ,
missingParameter ,
parameterOutOfRange ,
systemFailure ,
taskRefused ,
unexpectedComponentSequence ,
unexpectedDataValue ,
unexpectedParameter
}

-- Direction: SSF ® SCF, Timer: Trsf
-- This operation is used to indicate that the SSP is unable to select a route (e.g. unable to determine a
-- correct route, no more routes on route list) or indication from the terminating half BCSM that a call
-- cannot be presented to the terminating party (e.g. network congestion) (DP – Route_Select_Failure).
-- For additional information on this operation, refer to Rec. Q.1224.
RouteSelectFailureArg ::= SEQUENCE {
dpSpecificCommonParameters [0] DpSpecificCommonParameters, 
dialledDigits [1] CalledPartyNumber OPTIONAL,
callingPartyBusinessGroupID [2] CallingPartyBusinessGroupID OPTIONAL,
callingPartySubaddress [3] CallingPartySubaddress OPTIONAL,
callingFacilityGroup [4] FacilityGroup OPTIONAL,
callingFacilityGroupMember [5] FacilityGroupMember OPTIONAL,
failureCause [6] Cause OPTIONAL,
originalCalledPartyID [7] OriginalCalledPartyID OPTIONAL,
prefix [8] Digits OPTIONAL,
redirectingPartyID [9] RedirectingPartyID OPTIONAL,
redirectionInformation [10] RedirectionInformation OPTIONAL,
routeList [11] RouteList OPTIONAL,
travellingClassMark [12] TravellingClassMark OPTIONAL,
extensions [13] SEQUENCE SIZE(1..numOfExtensions) OF
ExtensionField OPTIONAL,
carrier [14] Carrier OPTIONAL
}
-- For the OPTIONAL parameters, refer to clause 17 for the trigger detection point processing
-- rules to specify when these parameters are included in the message.
SelectFacility ::= OPERATION
ARGUMENT SelectFacilityArg 
-- RETURN RESULT FALSE
ERRORS {missingParameter ,
parameterOutOfRange ,
systemFailure ,
taskRefused ,
unexpectedComponentSequence ,
unexpectedDataValue ,
unexpectedParameter
}

-- Direction: SCF ® SSF, Timer: Tsf
-- This operation is used to request the SSF to perform the terminating basic call processing
-- actions to select the terminating line if it is idle, or select an idle line from a multi-line hunt
-- group, or select an idle trunk from a trunk group, as appropriate. If no idle line or trunk is
-- available, the SSF determines that the terminating facility is busy.
SelectFacilityArg ::= SEQUENCE {
alertingPattern [0] AlertingPattern OPTIONAL,
destinationNumberRoutingAddress [1] CalledPartyNumber OPTIONAL,
iSDNAccessRelatedInformation [2] ISDNAccessRelatedInformation OPTIONAL,
calledFacilityGroup [3] FacilityGroup OPTIONAL,
calledFacilityGroupMember [4] FacilityGroupMember OPTIONAL,
originalCalledPartyID [5] OriginalCalledPartyID OPTIONAL,
extensions [6] SEQUENCE SIZE(1..numOfExtensions) OF
ExtensionField OPTIONAL,
displayInformation [7] DisplayInformation OPTIONAL,
serviceInteractionIndicators [8] ServiceInteractionIndicators OPTIONAL,
iNServiceCompatibilityResponse [9] INServiceCompatibilityResponse OPTIONAL,
forwardGVNS [10] ForwardGVNS OPTIONAL,
backwardGVNS [11] BackwardGVNS OPTIONAL,
serviceInteractionIndicatorsTwo [12] ServiceInteractionIndicatorsTwo OPTIONAL,
correlationID [13] CorrelationID OPTIONAL,
scfID [14] ScfID OPTIONAL,
callSegmentID [15] CallSegmentID OPTIONAL,
legToBeCreated [16] LegID OPTIONAL
}
-- OPTIONAL parameters are only provided when modifiying basic call processing values.
SelectRoute ::= OPERATION
ARGUMENT SelectRouteArg 
-- RETURN RESULT FALSE
ERRORS {missingParameter ,
parameterOutOfRange ,
systemFailure ,
taskRefused ,
unexpectedComponentSequence ,
unexpectedDataValue ,
unexpectedParameter
}

-- Direction: SCF ® SSF, Timer: Tsr
-- This operation is used to request the SSF to perform the originating basic call processing actions to
-- determine routing information and select a route for a call, based either on call information available
-- to the SSF, or on call information provided by the SCF (e.g. for alternate routing), to include the
-- called party address, type of call, carrier, route index, and one or more alternate route indices.
-- Based on the routing information, the SSF attempts to select a primary route for the call, and if the
-- route is busy, attempts to select an alternate route. The SSF may fail to select a route for the call
-- if all routes are busy.
SelectRouteArg ::= SEQUENCE {
destinationRoutingAddress [0] DestinationRoutingAddress ,
alertingPattern [1] AlertingPattern OPTIONAL,
correlationID [2] CorrelationID OPTIONAL,
iSDNAccessRelatedInformation [3] ISDNAccessRelatedInformation OPTIONAL,
originalCalledPartyID [4] OriginalCalledPartyID OPTIONAL,
routeList [5] RouteList OPTIONAL,
scfID [6] ScfID OPTIONAL,
travellingClassMark [7] TravellingClassMark OPTIONAL,
extensions [8] SEQUENCE SIZE(1..numOfExtensions)OF
ExtensionField OPTIONAL,
carrier [9] Carrier OPTIONAL,
serviceInteractionIndicators [10] ServiceInteractionIndicators OPTIONAL,
iNServiceCompatibilityResponse [11] INServiceCompatibilityResponse OPTIONAL,
forwardGVNS [12] ForwardGVNS OPTIONAL,
backwardGVNS [13] BackwardGVNS OPTIONAL,
serviceInteractionIndicatorsTwo [14] ServiceInteractionIndicatorsTwo OPTIONAL,
callSegmentID [15] CallSegmentID OPTIONAL,
legToBeCreated [16] LegID OPTIONAL
}
-- OPTIONAL parameters are only provided when modifiying basic call processing values.
SendChargingInformation ::= OPERATION
ARGUMENT SendChargingInformationArg 
-- RETURN RESULT FALSE
ERRORS {missingParameter ,
unexpectedComponentSequence ,
unexpectedParameter ,
parameterOutOfRange ,
systemFailure ,
taskRefused ,
unknownLegID
}

-- Direction: SCF ® SSF, Timer: Tsci
-- This operation is used to instruct the SSF on the charging information to send by the SSF.
-- The charging information can either be sent back by means of signalling or internal
-- if the SSF is located in the local exchange. In the local exchange,
-- this information may be used to update the charge meter or to create a standard call record.
SendChargingInformationArg ::= SEQUENCE {
sCIBillingChargingCharacteristics [0] SCIBillingChargingCharacteristics, 
partyToCharge [1] LegID,
extensions [2] SEQUENCE SIZE(1..numOfExtensions) OF
ExtensionField OPTIONAL
}

SendFacilityInformation ::= OPERATION
ARGUMENT SendFacilityInformationArg 
-- RETURN RESULT FALSE
ERRORS {missingParameter ,
unexpectedComponentSequence ,
unexpectedParameter ,
unexpectedDataValue ,
systemFailure ,
taskRefused ,
unknownLegID
}

-- Direction: SCF ® SSF, Timer: Tsfi
-- This operation is issued by the SCF during a BCSM being suspended at a DP to request the CCF/SSF
-- sending a FACILITY IE to a user with a specified DSS 1 message.
SendFacilityInformationArg ::= SEQUENCE{
componentType [0] ComponentType,
legID [1] LegID OPTIONAL,
componentCorrelationID [2] ComponentCorrelationID OPTIONAL,
component [3] Component,
callProcessingOperationCorrelationID [4] CallProcessingOperationCorrelationID
DEFAULT fACility,
extensions [5] SEQUENCE SIZE(1..numOfExtensions) OF
ExtensionField OPTIONAL
}
-- FACILITY IE will be delivered with the specified DSS 1 message. The message is specified with the
-- callProcessingOperationCorrelationID
SendSTUI ::= OPERATION
ARGUMENT SendSTUIArg 
-- RETURN RESULT FALSE
ERRORS {missingParameter ,
parameterOutOfRange ,
unexpectedComponentSequence ,
unexpectedParameter ,
unexpectedDataValue ,
systemFailure ,
taskRefused ,
unknownLegID
}

-- Direction: SCF ® SSF, Timer: Tss
-- This operation is issued by the SCF in the context of the USI feature. It is used to request the SSF
-- to send a Service to User Information (STUI) information element to the indicated user.
SendSTUIArg ::= SEQUENCE {
uSIServiceIndicator [0] USIServiceIndicator, 
legID [1] LegID DEFAULT sendingSideID:leg1,
uSIInformation [2] USIInformation ,
extensions [3] SEQUENCE SIZE(1..numOfExtensions) OF
ExtensionField OPTIONAL
}

ServiceFilteringResponse ::= OPERATION
ARGUMENT ServiceFilteringResponseArg 
-- RETURN RESULT FALSE
--ALWAYS RESPONDS FALSE

-- Direction: SSF ® SCF, Timer: Tsfr
-- This operation is used to send back to the SCF the values of counters specified in a previous
-- ActivatedServiceFiltering operation
ServiceFilteringResponseArg ::= SEQUENCE {
countersValue [0] CountersValue,
filteringCriteria [1] FilteringCriteria ,
extensions [2] SEQUENCE SIZE(1..numOfExtensions)OF
ExtensionField OPTIONAL,
responseCondition [3] ResponseCondition OPTIONAL
}

SplitLeg ::= OPERATION
ARGUMENT SplitLegArg 
-- RETURN RESULT TRUE
ERRORS {missingParameter ,
unexpectedComponentSequence ,
unexpectedParameter ,
unexpectedDataValue ,
systemFailure ,
taskRefused ,
unknownLegID
}

-- Direction: SCF ® SSF, Timer: Tsl
-- This operation is issued by the SCF to separate one joined leg from a multi-way connection
-- or to interrupt the bearer connection between the involved legs of a single two party Call segment.
SplitLegArg ::= SEQUENCE {
legToBeSplit [0] LegID,
newCallSegment [1] INTEGER (2..numOfCSs),
extensions [2] SEQUENCE SIZE (1..numOfExtensions) OF
ExtensionField OPTIONAL
}

StatusReport ::= OPERATION
ARGUMENT StatusReportArg 
-- RETURN RESULT FALSE
--ALWAYS RESPONDS FALSE

-- Direction: SSF ® SCF, Timer: Tsrp
-- This operation is used as a response to RequestFirstStatusMatchReport or
-- RequestEveryStatusChangeReport operations.
StatusReportArg ::= SEQUENCE {
resourceStatus [0] ResourceStatus OPTIONAL,
correlationID [1] CorrelationID OPTIONAL,
resourceID [2] ResourceID OPTIONAL,
extensions [3] SEQUENCE SIZE(1..numOfExtensions)OF
ExtensionField OPTIONAL,
reportCondition [4] ReportCondition OPTIONAL
}
-- For correlationID, OPTIONAL denotes network-operator optional.
-- resourceID is required when the SSF sends a report as an answer to a previous request when the
-- correlationID was present.
TAnswer ::= OPERATION
ARGUMENT TAnswerArg 
-- RETURN RESULT FALSE
ERRORS {missingCustomerRecord ,
missingParameter ,
parameterOutOfRange ,
unexpectedComponentSequence ,
unexpectedParameter ,
unexpectedDataValue ,
systemFailure ,
taskRefused
}

-- Direction: SSF ® SCF, Timer: Tta
-- This operation is used to indicate that the call is accepted and answered by terminating party
-- (e.g. terminating party goes off-hook, Q.931 Connect message received, ISDN-UP Answer message
-- received) (DP – T_Answer). For additional information on this operation, refer to Rec. Q.1224.
TAnswerArg ::= SEQUENCE {
dpSpecificCommonParameters [0] DpSpecificCommonParameters, 
calledPartyBusinessGroupID [1] CalledPartyBusinessGroupID OPTIONAL,
calledPartySubaddress [2] CalledPartySubaddress OPTIONAL,
calledFacilityGroup [3] FacilityGroup OPTIONAL,
calledFacilityGroupMember [4] FacilityGroupMember OPTIONAL,
extensions [5] SEQUENCE SIZE(1..numOfExtensions)OF
ExtensionField OPTIONAL,
componentType [6] ComponentType OPTIONAL,
component [7] Component OPTIONAL,
componentCorrelationID [8] ComponentCorrelationID OPTIONAL
}

TBusy ::= OPERATION
ARGUMENT TBusyArg 
-- RETURN RESULT FALSE
ERRORS {missingCustomerRecord ,
missingParameter ,
parameterOutOfRange ,
unexpectedComponentSequence ,
unexpectedParameter ,
unexpectedDataValue ,
systemFailure ,
taskRefused }

-- Direction: SSF ® SCF, Timer: Ttb
-- This operation is used to indicate all resources in group busy (DP– TBusy).
-- For additional information on this operation, refer to Rec. Q.1224.
TBusyArg ::= SEQUENCE {
dpSpecificCommonParameters [0] DpSpecificCommonParameters ,
busyCause [1] Cause OPTIONAL,
calledPartyBusinessGroupID [2] CalledPartyBusinessGroupID OPTIONAL,
calledPartySubaddress [3] CalledPartySubaddress OPTIONAL,
originalCalledPartyID [4] OriginalCalledPartyID OPTIONAL,
redirectingPartyID [5] RedirectingPartyID OPTIONAL,
redirectionInformation [6] RedirectionInformation OPTIONAL,
routeList [7] RouteList OPTIONAL,
travellingClassMark [8] TravellingClassMark OPTIONAL,
extensions [9] SEQUENCE SIZE(1..numOfExtensions)OF
ExtensionField OPTIONAL
}
-- For the OPTIONAL parameters, refer to clause 17 for the trigger detection point processing rules
-- to specify when these parameters are included in the message.
TDisconnect ::= OPERATION 
ARGUMENT TDisconnectArg 
-- RETURN RESULT FALSE
ERRORS {missingCustomerRecord ,
missingParameter ,
parameterOutOfRange ,
unexpectedComponentSequence ,
unexpectedParameter ,
unexpectedDataValue ,
systemFailure ,
taskRefused }

-- Direction: SSF ® SCF, Timer: Ttd
-- This operation is used for a disconnect indication (e.g. on-hook, Q.931 Disconnect message,
-- SS7 Release message) is received from the terminating party, or received from the originating party
-- via the originating half BCSM. (DP – T_Disconnect). For additional information on this operation,
-- refer to Rec. Q.1224.
TDisconnectArg ::= SEQUENCE {
dpSpecificCommonParameters [0] DpSpecificCommonParameters, 
calledPartyBusinessGroupID [1] CalledPartyBusinessGroupID OPTIONAL,
calledPartySubaddress [2] CalledPartySubaddress OPTIONAL,
calledFacilityGroup [3] FacilityGroup OPTIONAL,
calledFacilityGroupMember [4] FacilityGroupMember OPTIONAL,
releaseCause [5] Cause OPTIONAL,
extensions [6] SEQUENCE SIZE(1..numOfExtensions)OF
ExtensionField OPTIONAL,
connectTime [7] Integer4 OPTIONAL,
componentType [8] ComponentType OPTIONAL,
component [9] Component OPTIONAL,
componentCorrelationID [10] ComponentCorrelationID OPTIONAL
}

TermAttemptAuthorized ::= OPERATION
ARGUMENT TermAttemptAuthorizedArg 
-- RETURN RESULT FALSE
ERRORS {missingCustomerRecord ,
missingParameter ,
parameterOutOfRange ,
unexpectedComponentSequence ,
unexpectedParameter ,
unexpectedDataValue ,
systemFailure ,
taskRefused }


-- Direction: SSF ® SCF, Timer: Ttaa
-- This operation is used for indication of incoming call received from originating half BCSM and authority
-- to route call to a specified terminating resource (or group) verified. (DP – Termination_Authorized).
-- For additional information on this operation, refer to Rec. Q.1224.
TermAttemptAuthorizedArg ::= SEQUENCE {
dpSpecificCommonParameters [0] DpSpecificCommonParameters, 
calledPartyBusinessGroupID [1] CalledPartyBusinessGroupID OPTIONAL,
calledPartySubaddress [2] CalledPartySubaddress OPTIONAL,
callingPartyBusinessGroupID [3] CallingPartyBusinessGroupID OPTIONAL,
originalCalledPartyID [4] OriginalCalledPartyID OPTIONAL,
redirectingPartyID [5] RedirectingPartyID OPTIONAL,
redirectionInformation [6] RedirectionInformation OPTIONAL,
routeList [7] RouteList OPTIONAL,
travellingClassMark [8] TravellingClassMark OPTIONAL,
extensions [9] SEQUENCE SIZE(1..numOfExtensions)OF
ExtensionField OPTIONAL,
callingPartySubaddress [10] CallingPartySubaddress OPTIONAL
}

TerminationAttempt ::= OPERATION
ARGUMENT TerminationAttemptArg 
-- RETURN RESULT FALSE
ERRORS {missingCustomerRecord ,
missingParameter ,
parameterOutOfRange ,
unexpectedComponentSequence ,
unexpectedParameter ,
unexpectedDataValue ,
systemFailure ,
taskRefused }

-- Direction: SSF ® SCF, Timer: Ttra
-- This operation is used for indication of a call termination attempt from the terminating half BCSM. (DP –
-- Termination_Attempt).
-- For additional information on this operation, refer to Rec. Q.1224.
TerminationAttemptArg ::= SEQUENCE {
dpSpecificCommonParameters [0] DpSpecificCommonParameters ,
calledPartyBusinessGroupID [1] CalledPartyBusinessGroupID OPTIONAL,
calledPartySubaddress [2] CalledPartySubaddress OPTIONAL,
callingPartyBusinessGroupID [3] CallingPartyBusinessGroupID OPTIONAL,
callingPartySubaddress [4] CallingPartySubaddress OPTIONAL,
originalCalledPartyID [5] OriginalCalledPartyID OPTIONAL,
redirectingPartyID [6] RedirectingPartyID OPTIONAL,
redirectionInformation [7] RedirectionInformation OPTIONAL,
routeList [8] RouteList OPTIONAL,
travellingClassMark [9] TravellingClassMark OPTIONAL,
extensions [10] SEQUENCE SIZE(1..numOfExtensions) OF
ExtensionField OPTIONAL
}
-- For the OPTIONAL parameters, refer to clause 17 for the trigger detection point processing rules
-- to specify when these parameters are included in the message.

TMidCall ::= OPERATION
ARGUMENT MidCallArg 
-- RETURN RESULT FALSE
ERRORS {missingCustomerRecord ,
missingParameter ,
parameterOutOfRange ,
unexpectedComponentSequence ,
unexpectedParameter ,
unexpectedDataValue ,
systemFailure ,
taskRefused }

-- Direction: SSF ® SCF, Timer: Ttmc
-- This operation is used to indicate that a feature request is received from the terminating party (e.g. hook
-- flash, ISDN feature activation Q.931 HOLD or RETrieve message). (DP – T_Mid_Call).
-- For additional information on this operation, refer to Rec. Q.1224.
TNoAnswer ::= OPERATION
ARGUMENT TNoAnswerArg 
-- RETURN RESULT FALSE
ERRORS {missingCustomerRecord ,
missingParameter ,
parameterOutOfRange ,
unexpectedComponentSequence ,
unexpectedParameter ,
unexpectedDataValue ,
systemFailure ,
taskRefused }

-- Direction: SSF ® SCF, Timer: Ttna
-- This operation is used to indicate that the terminating party does not answer within a specified duration.
-- (DP – T_No_Answer). For additional information on this operation, refer to Rec. Q.1224.
TNoAnswerArg ::= SEQUENCE {
dpSpecificCommonParameters [0] DpSpecificCommonParameters, 
calledPartyBusinessGroupID [1] CalledPartyBusinessGroupID OPTIONAL,
calledPartySubaddress [2] CalledPartySubaddress OPTIONAL,
calledFacilityGroup [3] FacilityGroup OPTIONAL,
calledFacilityGroupMember [4] FacilityGroupMember OPTIONAL,
originalCalledPartyID [5] OriginalCalledPartyID OPTIONAL,
redirectingPartyID [6] RedirectingPartyID OPTIONAL,
redirectionInformation [7] RedirectionInformation OPTIONAL,
travellingClassMark [8] TravellingClassMark OPTIONAL,
extensions [9] SEQUENCE SIZE(1..numOfExtensions)OF
ExtensionField OPTIONAL,
componentType [10] ComponentType OPTIONAL,
component [11] Component OPTIONAL,
componentCorrelationID [12] ComponentCorrelationID OPTIONAL
}

TSuspended ::= OPERATION
ARGUMENT TSuspendedArg 
-- RETURN RESULT FALSE
ERRORS {missingCustomerRecord ,
missingParameter ,
systemFailure ,
taskRefused ,
unexpectedComponentSequence ,
unexpectedDataValue ,
unexpectedParameter
}

-- Direction: SSF ® SCF, Timer: Tts
-- This operation is issued by the SSF after detecting a valid trigger condition at the T_Suspended DP or to
-- report a tSuspended event requested by the RequestReportBCSMEvent. For additional information on
-- this operation, refer to Rec. Q.1224.
TSuspendedArg ::= SEQUENCE {
dpSpecificCommonParameters [0] DpSpecificCommonParameters, 
legID [1] LegID OPTIONAL,
extensions [2] SEQUENCE SIZE(1..numOfExtensions)OF
ExtensionField OPTIONAL
}
-- For the OPTIONAL parameters, refer to clause 17 for the trigger detection point processing rules
-- to specify when these parameters are included in the message.
-- Use for T/EDP-R is ffs.
numOfCSs INTEGER::=4
numOfLegs INTEGER::=4
numOfChargingEvents INTEGER::= 5
numOfBCSMEvents INTEGER::= 9
numOfExtensions INTEGER::= 5
END
